from pivy_trackers.examples.select_drag_linked.select_drag_linked_tracker import SelectDragLinkedTracker
tracker = SelectDragLinkedTracker(Gui.ActiveDocument.ActiveView, is_linked=True, has_markers=False)
tracker.insert_into_scenegraph(True)
